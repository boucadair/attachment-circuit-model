module ietf-ac-common {
  yang-version 1.1;
  namespace "urn:ietf:params:xml:ns:yang:ietf-ac-common";
  prefix ac-common;

  import ietf-vpn-common {
    prefix vpn-common;
    reference
      "RFC 9181: A Common YANG Data Model for Layer 2 and Layer 3
                 VPNs";
  }
  import ietf-netconf-acm {
    prefix nacm;
    reference
      "RFC 8341: Network Configuration Access Control Model";
  }
  import ietf-inet-types {
    prefix inet;
    reference
      "RFC 6991: Common YANG Data Types, Section 4";
  }
  import ietf-yang-types {
    prefix yang;
    reference
      "RFC 6991: Common YANG Data Types, Section 3";
  }
  import ietf-key-chain {
    prefix key-chain;
    reference
      "RFC 8177: YANG Data Model for Key Chains";
  }

  organization
    "IETF OPSAWG (Operations and Management Area Working Group)";
  contact
    "WG Web:   <https://datatracker.ietf.org/wg/opsawg/>
     WG List:  <mailto:opsawg@ietf.org>

     Editor:   Mohamed Boucadair
               <mailto:mohamed.boucadair@orange.com>
     Author:   Richard Roberts
               <mailto:rroberts@juniper.net>
     Author:   Oscar Gonzalez de Dios
               <mailto:oscar.gonzalezdedios@telefonica.com>
     Author:   Samier Barguil
               <mailto:ssamier.barguil_giraldo@nokia.com>
     Author:   Bo Wu
               <mailto:lana.wubo@huawei.com>";
  description
    "This YANG module defines a common attachment circuit (AC)
     YANG model with a set of reusable features, types,
     identities, and groupings.

     Copyright (c) 2025 IETF Trust and the persons identified as
     authors of the code. All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see the
     RFC itself for full legal notices.";

  revision 2025-01-07 {
    description
      "Initial revision.";
    reference
      "RFC XXXX: A Common YANG Data Model for Attachment Circuits";
  }

  /****************************Features************************/
  
  feature layer2-ac {
    description
      "Indicates support of Layer 2 ACs.";
  }

  feature layer3-ac {
    description
      "Indicates support of Layer 3 ACs.";
  }

  feature server-assigned-reference {
    description
      "Indicates support for server-generated references and use
       of such references to access related resources.";
  }

  /****************************Identities************************/
  // IP address allocation types

  identity address-allocation-type {
    description
      "Base identity for address allocation type on the AC.";
  }

  identity provider-dhcp {
    base address-allocation-type;
    description
      "The provider's network provides a DHCP service to the
       customer.";
  }

  identity provider-dhcp-relay {
    base address-allocation-type;
    description
      "The provider's network provides a DHCP relay service to the
       customer.";
  }

  identity provider-dhcp-slaac {
    if-feature "vpn-common:ipv6";
    base address-allocation-type;
    description
      "The provider's network provides a DHCP service to the customer
       as well as IPv6 Stateless Address Autoconfiguration (SLAAC).";
    reference
      "RFC 4862: IPv6 Stateless Address Autoconfiguration";
  }

  identity static-address {
    base address-allocation-type;
    description
      "The provider's network provides static IP addressing to the
       customer.";
  }

  identity slaac {
    if-feature "vpn-common:ipv6";
    base address-allocation-type;
    description
      "The provider's network uses IPv6 SLAAC to provide addressing
       to the customer.";
    reference
      "RFC 4862: IPv6 Stateless Address Autoconfiguration";
  }

  identity dynamic-infra {
    base address-allocation-type;
    description
      "The IP address is dynamically allocated by the hosting
       infrastructure.";
  }

  // next-hop actions 

  identity local-defined-next-hop {
    description
      "Base identity of local defined next hops.";
  }

  identity discard {
    base local-defined-next-hop;
    description
      "Indicates an action to discard traffic for the corresponding
       destination. For example, this can be used to black-hole
       traffic.";
  }

  identity local-link {
    base local-defined-next-hop;
    description
      "Treat traffic towards addresses within the specified next-hop
       prefix as though they are connected to a local link.";
  }

  // Layer 2 tunnel types

  identity l2-tunnel-type {
    description
      "Base identity for Layer 2 tunnel selection for an AC.";
  }

  identity pseudowire {
    base l2-tunnel-type;
    description
      "Pseudowire tunnel termination for the AC.";
  }

  identity vpls {
    base l2-tunnel-type;
    description
      "Virtual Private LAN Service (VPLS) tunnel termination for
       the AC.";
  }

  identity vxlan {
    base l2-tunnel-type;
    description
      "Virtual eXtensible Local Area Network (VXLAN) tunnel
       termination for the AC.";
  }

  // Layer 3 tunnel types

  identity l3-tunnel-type {
    description
      "Base identity for Layer 3 tunnel selection for an AC.";
  }

  identity ip-in-ip {
    base l3-tunnel-type;
    description
      "IP in IP Tunneling.";
    reference
      "RFC 2003: IP Encapsulation within IP";
  }

  identity ipsec {
    base l3-tunnel-type;
    description
      "IP Security (IPsec).";
    reference
      "RFC 4301: Security Architecture for the Internet
                 Protocol";
  }

  identity gre {
    base l3-tunnel-type;
    description
      "Generic Routing Encapsulation (GRE).";
    reference
      "RFC 1701: Generic Routing Encapsulation (GRE)
       RFC 1702: Generic Routing Encapsulation over IPv4 networks
       RFC 7676: IPv6 Support for Generic Routing Encapsulation
                 (GRE)";
  }

  // Tagging precedence

  identity precedence-type {
    description
      "Redundancy type. Attachment to a network can be created
       with primary and secondary tagging.";
  }

  identity primary {
    base precedence-type;
    description
      "Identifies the main attachment circuit.";
  }

  identity secondary {
    base precedence-type;
    description
      "Identifies a secondary attachment circuit.";
  }

  // AC type

  identity role {
    description
      "Base identity for the network role of an AC.";
  }

  identity uni {
    base role;
      description
        "User-to-Network Interface (UNI).";
  }

  identity nni {
    base role;
    description
      "Network-to-Network Interface (NNI).";
  }

  identity public-nni {
    base role;
    description
      "Public peering. This is typically set using a shared
       network, such as an Internet Exchange Point (IXP).";
  }

  // More Admin status types

  identity awaiting-validation {
    base vpn-common:administrative-status;
    description
      "This administrative status reflects that a request is
       pending an administrator approval.";
  }

  identity awaiting-processing {
    base vpn-common:administrative-status;
    description
      "This administrative status reflects that a request was
       approved and validated, but is awaiting more processing
       before activation.";
  }

  identity admin-prohibited {
    base vpn-common:administrative-status;
    description
      "This administrative status reflects that a request cannot
       be handled because of administrative policies.";
  }

  identity rejected {
    base vpn-common:administrative-status;
    description
      "This administrative status reflects that a request was
       rejected because, e.g., there are no sufficient resources
       or other reasons not covered by the other status types.";
  }

  // BGP role

  identity bgp-role {
    description
      "Used to indicate BGP role when establishing a BGP session.";
    reference
      "RFC 9234: Route Leak Prevention and Detection Using 
                 Roles in UPDATE and OPEN Messages, Section 4";
  }

  identity provider {
    base bgp-role;
    description
      "The local AS is a transit provider of the remote AS.";
  }

  identity client {
    base bgp-role;
    description
      "The local AS is a transit customer of the remote AS.";
  }

  identity rs {
    base bgp-role;
    description
      "The local AS is a Route Server (RS).";
  }

  identity rs-client {
    base bgp-role;
    description
      "The local AS is a client of an RS and the RS is the
       remote AS.";
  }

  identity peer {
    base bgp-role;
    description
      "The local and remote ASes have a peering relationship.";
  }

  /****************************Typedefs************************/

  typedef predefined-next-hop {
    type identityref {
      base local-defined-next-hop;
    }
    description
      "Predefined next-hop designation for locally generated
       routes.";
  }

  typedef area-address {
    type string {
      pattern '[0-9A-Fa-f]{2}(\.[0-9A-Fa-f]{4}){0,6}';
    }
    description
      "This type defines the area address format.";
  }

  /************************Reusable groupings********************/
  /**** Service Status ****/

  grouping service-status {
    description
      "Service status grouping.";
    container status {
      description
        "Service status.";
      container admin-status {
        description
          "Administrative service status.";
        leaf status {
          type identityref {
            base vpn-common:administrative-status;
          }
          description
            "Administrative service status.";
        }
        leaf last-change {
          type yang:date-and-time;
          config false;
          description
            "Indicates the actual date and time of the service status
             change.";
        }
      }
      container oper-status {
        config false;
        description
          "Operational service status.";
        uses vpn-common:oper-status-timestamp;
      }
    }
  }

  /**** A set of profiles ****/

  grouping ac-profile-cfg {
    description
      "Grouping for AC profile configuration.";
    container valid-provider-identifiers {
      description
        "Container for valid provider profile identifiers.
         The profiles only have significance within the service
         provider's administrative domain.";
      list encryption-profile-identifier {
        key "id";
        description
          "List of encryption profile identifiers.";
        leaf id {
          type string;
          description
            "Identification of the encryption profile to be used.";
        }
      }
      list qos-profile-identifier {
        key "id";
        description
          "List of QoS profile identifiers.";
        leaf id {
          type string;
          description
            "Identification of the QoS profile to be used.";
        }
      }
      list failure-detection-profile-identifier {
        key "id";
        description
          "List of BFD profile identifiers.";
        leaf id {
          type string;
          description
            "Identification of the failure detection (e.g., BFD)
             profile to be used.";
        }
      }
      list forwarding-profile-identifier {
        key "id";
        description
          "List of forwarding profile identifiers.";
        leaf id {
          type string;
          description
            "Identification of the forwarding profile to be used.";
        }
      }
      list routing-profile-identifier {
        key "id";
        description
          "List of routing profile identifiers.";
        leaf id {
          type string;
          description
            "Identification of the routing profile to be used by
             the routing protocols over an AC.";
        }
      }
      nacm:default-deny-write;
    }
  }

  /**** Operational instructions ****/

  grouping op-instructions {
    description
      "Scheduling instructions.";
    leaf requested-start {
      type yang:date-and-time;
      description
        "Indicates the requested date and time when the service is
         expected to be active.";
    }
    leaf requested-stop {
      type yang:date-and-time;
      description
        "Indicates the requested date and time when the service is
         expected to be disabled.";
    }
    leaf actual-start {
      type yang:date-and-time;
      config false;
      description
        "Indicates the actual date and time when the service
         actually was enabled.";
    }
    leaf actual-stop {
      type yang:date-and-time;
      config false;
      description
        "Indicates the actual date and time when the service
         actually was disabled.";
    }
  }

  /**** Layer 2 encapsulations ****/
  // Dot1q

  grouping dot1q {
    description
      "Defines a grouping for tagged interfaces.";
    leaf tag-type {
      type identityref {
        base vpn-common:tag-type;
      }
      description
        "Tag type.";
    }
    leaf cvlan-id {
      type uint16 {
        range "1..4094";
      }
      description
        "VLAN identifier.";
    }
  }

  // priority-tagged

  grouping priority-tagged {
    description
      "Priority tagged.";
    leaf tag-type {
      type identityref {
        base vpn-common:tag-type;
      }
      description
        "Tag type.";
    }
  }

  // QinQ

  grouping qinq {
    description
      "Includes QinQ parameters.";
    leaf tag-type {
      type identityref {
        base vpn-common:tag-type;
      }
      description
        "Tag type.";
    }
    leaf svlan-id {
      type uint16 {
        range "1..4094";
      }
      description
        "Service VLAN (S-VLAN) identifier.";
    }
    leaf cvlan-id {
      type uint16 {
        range "1..4094";
      }
      description
        "Customer VLAN (C-VLAN) identifier.";
    }
  }

  /**** Layer 2 tunnel services ****/
  // pseudowire (PW)

  grouping pseudowire {
    description
      "Includes pseudowire termination parameters.";
    leaf vcid {
      type uint32;
      description
        "Indicates a PW or virtual circuit (VC) identifier.";
    }
    leaf far-end {
      type union {
        type uint32;
        type inet:ip-address;
      }
      description
        "Neighbor reference.";
      reference
        "RFC 8077: Pseudowire Setup and Maintenance Using the Label
                   Distribution Protocol (LDP), Section 6.1";
    }
  }

  // VPLS

  grouping vpls {
    description
      "VPLS termination parameters.";
    leaf vcid {
      type uint32;
      description
        "VC identifier.";
    }
    leaf-list far-end {
      type union {
        type uint32;
        type inet:ip-address;
      }
      description
        "Neighbor reference.";
    }
  }

  // VXLAN

  grouping vxlan {
    description
      "VXLAN termination parameters.";
    leaf vni-id {
      type uint32;
      description
        "VXLAN Network Identifier (VNI).";
    }
    leaf peer-mode {
      type identityref {
        base vpn-common:vxlan-peer-mode;
      }
      description
        "Specifies the VXLAN access mode. By default, the peer mode
         is set to 'static-mode'.";
    }
    leaf-list peer-ip-address {
      type inet:ip-address;
      description
        "List of a peer's IP addresses.";
    }
  }

  // Layer 2 Tunnel service

  grouping l2-tunnel-service {
    description
      "Defines a Layer 2 tunnel termination.";
    leaf type {
      type identityref {
        base l2-tunnel-type;
      }
      description
        "Selects the tunnel termination type for an AC.";
    }
    container pseudowire {
      when "derived-from-or-self(../type, 'ac-common:pseudowire')" {
        description
          "Only applies when the Layer 2 service type is
           'pseudowire'.";
      }
      description
        "Includes pseudowire termination parameters.";
      uses pseudowire;
    }
    container vpls {
      when "derived-from-or-self(../type, 'ac-common:vpls')" {
        description
          "Only applies when the Layer 2 service type is 'vpls'.";
      }
      description
        "VPLS termination parameters.";
      uses vpls;
    }
    container vxlan {
      when "derived-from-or-self(../type, 'ac-common:vxlan')" {
        description
          "Only applies when the Layer 2 service type is 'vxlan'.";
      }
      description
        "VXLAN termination parameters.";
      uses vxlan;
    }
  }

  /**** Layer 3 connection *****/
  // IPv4 allocation type

  grouping ipv4-allocation-type {
    description
      "IPv4-specific parameters.";
    leaf prefix-length {
      type uint8 {
        range "0..32";
      }
      description
        "Subnet prefix length expressed in bits. It is applied to
         both local and customer addresses.";
    }
    leaf address-allocation-type {
      type identityref {
        base address-allocation-type;
      }
      must "not(derived-from-or-self(current(), 'ac-common:slaac') "
         + "or derived-from-or-self(current(), "
         + "'ac-common:provider-dhcp-slaac'))" {
        error-message "SLAAC is only applicable to IPv6.";
      }
      description
        "Defines how IPv4 addresses are allocated to the peer
         termination points.";
    }
  }

  // IPv6 allocation type

  grouping ipv6-allocation-type {
    description
      "IPv6-specific parameters.";
    leaf prefix-length {
      type uint8 {
        range "0..128";
      }
      description
        "Subnet prefix length expressed in bits. It is applied to
         both local and customer addresses.";
    }
    leaf address-allocation-type {
      type identityref {
        base address-allocation-type;
      }
      description
        "Defines how IPv6 addresses are allocated to the peer
         termination points.";
    }
  }

  // Basic parameters for an IPv4 connection 

  grouping ipv4-connection-basic {
    description
      "Basic set for IPv4-specific parameters for the connection.";
    uses ipv4-allocation-type;
    choice allocation-type {
      description
        "Choice of the IPv4 address allocation.";
      case dynamic {
        description
          "When the addresses are allocated by DHCP or other dynamic
           means local to the infrastructure.";
        choice provider-dhcp {
          description
            "Parameters related to DHCP-allocated addresses. IP
             addresses are allocated by DHCP, that is provided by
             the operator.";
          leaf dhcp-service-type {
            type enumeration {
              enum server {
                description
                  "Local DHCP server.";
              }
              enum relay {
                description
                  "Local DHCP relay. DHCP requests are relayed to
                   a provider's server.";
              }
            }
            description
              "Indicates the type of DHCP service to be enabled on
               an AC.";
          }
        }
        choice dhcp-relay {
          description
            "The DHCP relay is provided by the operator.";
          container customer-dhcp-servers {
            description
              "Container for a list of the customer's DHCP servers.";
            leaf-list server-ip-address {
              type inet:ipv4-address;
              description
                "IPv4 addresses of the customer's DHCP server.";
            }
          }
        }
      }
    }
  }

  // Basic parameters for an IPv6 connection

  grouping ipv6-connection-basic {
    description
      "Basic set for IPv6-specific parameters for the connection.";
    uses ipv6-allocation-type;
    choice allocation-type {
      description
        "Choice of the IPv6 address allocation.";
      case dynamic {
        description
          "When the addresses are allocated by DHCP or other dynamic
           means local to the infrastructure.";
        choice provider-dhcp {
          description
            "Parameters related to DHCP-allocated addresses.
             IP addresses are allocated by DHCP, that is provided
             by the operator.";
          leaf dhcp-service-type {
            type enumeration {
              enum server {
                description
                  "Local DHCP server.";
              }
              enum relay {
                description
                  "Local DHCP relay. DHCP requests are relayed to a
                   provider's server.";
              }
            }
            description
              "Indicates the type of DHCP service to be enabled on
               the AC.";
          }
        }
        choice dhcp-relay {
          description
            "The DHCP relay is provided by the operator.";
          container customer-dhcp-servers {
            description
              "Container for a list of the customer's DHCP servers.";
            leaf-list server-ip-address {
              type inet:ipv6-address;
              description
                "IPv6 addresses of the customer's DHCP server.";
            }
          }
        }
      }
    }
  }

  // Full parameters for the IPv4 connection

  grouping ipv4-connection {
    description
      "IPv4-specific connection parameters.";
    leaf local-address {
      type inet:ipv4-address;
      description
        "The IP address used at the provider's interface.";
    }
    leaf virtual-address {
      type inet:ipv4-address;
      description
        "This address may be used for redundancy purposes.";
    }
    uses ipv4-allocation-type;
    choice allocation-type {
      description
        "Choice of the IPv4 address allocation.";
      case dynamic {
        description
          "When the addresses are allocated by DHCP or other
           dynamic means local to the infrastructure.";
        choice address-assign {
          description
            "A choice for how IPv4 addresses are assigned.";
          case number {
            leaf number-of-dynamic-address {
              type uint16;
              description
                "Specifies the number of IP addresses to be assigned
                 to the customer on the AC.";
            }
          }
          case explicit {
            container customer-addresses {
              description
                "Container for customer addresses to be allocated
                 using DHCP.";
              list address-pool {
                key "pool-id";
                description
                  "Describes IP addresses to be dynamically
                   allocated.

                   When only 'start-address' is present, it
                   represents a single address.

                   When both 'start-address' and 'end-address' are
                   specified, it implies a range inclusive of both
                   addresses.";
                leaf pool-id {
                  type string;
                  description
                    "A pool identifier for the address range from
                     'start-address' to 'end-address'.";
                }
                leaf start-address {
                  type inet:ipv4-address;
                  mandatory true;
                  description
                    "Indicates the first address in the pool.";
                }
                leaf end-address {
                  type inet:ipv4-address;
                  description
                    "Indicates the last address in the pool.";
                }
              }
            }
          }
        }
        choice provider-dhcp {
          description
            "Parameters related to DHCP-allocated addresses. IP
             addresses are allocated by DHCP, which is provided by
             the operator.";
          leaf dhcp-service-type {
            type enumeration {
              enum server {
                description
                  "Local DHCP server.";
              }
              enum relay {
                description
                  "Local DHCP relay. DHCP requests are relayed to
                   a provider's server.";
              }
            }
            description
              "Indicates the type of DHCP service to be enabled on
               this AC.";
          }
        }
        choice dhcp-relay {
          description
            "The DHCP relay is provided by the operator.";
          container customer-dhcp-servers {
            description
              "Container for a list of the customer's DHCP servers.";
            leaf-list server-ip-address {
              type inet:ipv4-address;
              description
                "IPv4 addresses of the customer's DHCP server.";
            }
          }
        }
      }
      case static-addresses {
        description
          "Lists the IPv4 addresses that are used.";
        list address {
          key "address-id";
          ordered-by user;
          description
            "Lists the IPv4 addresses that are used. The first
             address of the list is the primary address of the
             connection.";
          leaf address-id {
            type string;
            description
              "An identifier of the static IPv4 address.";
          }
          leaf customer-address {
            type inet:ipv4-address;
            description
              "An IPv4 address of the customer side.";
          }
        }
      }
    }
  }

  // Full parameters for the IPv6 connection

  grouping ipv6-connection {
    description
      "IPv6-specific connection parameters.";
    leaf local-address {
      type inet:ipv6-address;
      description
        "IPv6 address of the provider side.";
    }
    leaf virtual-address {
      type inet:ipv6-address;
      description
        "This address may be used for redundancy purposes.";
    }
    uses ipv6-allocation-type;
    choice allocation-type {
      description
        "Choice of the IPv6 address allocation.";
      case dynamic {
        description
          "When the addresses are allocated by DHCP or other
           dynamic means local to the infrastructure.";
        choice address-assign {
          description
            "A choice for how IPv6 addresses are assigned.";
          case number {
            leaf number-of-dynamic-address {
              type uint16;
              description
                "Specifies the number of IP addresses to be
                 assigned to the customer on this access.";
            }
          }
          case explicit {
            container customer-addresses {
              description
                "Container for customer addresses to be allocated
                 using DHCP.";
              list address-pool {
                key "pool-id";
                description
                  "Describes IP addresses to be dynamically
                   allocated.

                   When only 'start-address' is present, it
                   represents a single address.

                   When both 'start-address' and 'end-address' are
                   specified, it implies a range inclusive of both
                   addresses.";
                leaf pool-id {
                  type string;
                  description
                    "A pool identifier for the address range from
                     'start-address' to 'end-address'.";
                }
                leaf start-address {
                  type inet:ipv6-address;
                  mandatory true;
                  description
                    "Indicates the first address in the pool.";
                }
                leaf end-address {
                  type inet:ipv6-address;
                  description
                    "Indicates the last address in the pool.";
                }
              }
            }
          }
        }
        choice provider-dhcp {
          description
            "Parameters related to DHCP-allocated addresses.
             IP addresses are allocated by DHCP, which is provided
             by the operator.";
          leaf dhcp-service-type {
            type enumeration {
              enum server {
                description
                  "Local DHCP server.";
              }
              enum relay {
                description
                  "Local DHCP relay. DHCP requests are relayed
                   to a provider's server.";
              }
            }
            description
              "Indicates the type of DHCP service to be enabled
               on this access.";
          }
        }
        choice dhcp-relay {
          description
            "The DHCP relay is provided by the operator.";
          container customer-dhcp-servers {
            description
              "Container for a list of the customer's DHCP servers.";
            leaf-list server-ip-address {
              type inet:ipv6-address;
              description
                "IPv6 addresses of the customer's DHCP server.";
            }
          }
        }
      }
      case static-addresses {
        description
          "Lists the IPv6 addresses that are used by the customer.";
        list address {
          key "address-id";
          ordered-by user;
          description
            "Lists the IPv6 addresses that are used. The first
             address of the list is the primary IP address of
             the connection.";
          leaf address-id {
            type string;
            description
              "An identifier of the static IPv6 address.";
          }
          leaf customer-address {
            type inet:ipv6-address;
            description
              "An IPv6 address of the customer side.";
          }
        }
      }
    }
  }

  /**** Routing ****/
  // Routing authentication

  grouping bgp-authentication {
    description
      "Grouping for BGP authentication parameters.";
    container authentication {
      description
        "Container for BGP authentication parameters.";
      leaf enabled {
        type boolean;
        description
          "Enables or disables authentication.";
      }
      container keying-material {
        when "../enabled = 'true'";
        description
          "Container for describing how a BGP routing session is to
           be secured on an AC.";
        choice option {
          description
            "Choice of authentication options.";
          case ao {
            description
              "Uses the TCP Authentication Option (TCP-AO).";
            reference
              "RFC 5925: The TCP Authentication Option";
            leaf enable-ao {
              type boolean;
              description
                "Enables the TCP-AO.";
            }
            leaf ao-keychain {
              type key-chain:key-chain-ref;
              description
                "Reference to the TCP-AO key chain.";
              reference
                "RFC 8177: YANG Data Model for Key Chains";
            }
          }
          case md5 {
            description
              "Uses MD5 to secure the session.";
            reference
              "RFC 4364: BGP/MPLS IP Virtual Private Networks
                         (VPNs), Section 13.2";
            leaf md5-keychain {
              type key-chain:key-chain-ref;
              description
                "Specifies a reference to the MD5 key chain.";
              reference
                "RFC 8177: YANG Data Model for Key Chains";
            }
          }
          case explicit {
            leaf key-id {
              type uint32;
              description
                "Specifies a key identifier.";
            }
            leaf key {
              type string;
              description
                "BGP authentication key.

                 This model only supports the subset of keys that
                 are representable as ASCII strings.";
            }
            leaf crypto-algorithm {
              type identityref {
                base key-chain:crypto-algorithm;
              }
              description
                "Indicates the cryptographic algorithm associated
                 with the key.";
            }
          }
        }
      }
    }
  }

  grouping ospf-authentication {
    description
      "Authentication configuration.";
    container authentication {
      description
        "Container for OSPF authentication parameters.";
      leaf enabled {
        type boolean;
        description
          "Enables or disables authentication.";
      }
      container keying-material {
        when "../enabled = 'true'";
        description
          "Container for describing how an OSPF session is to be
           secured for an AC.";
        choice option {
          description
            "Options for OSPF authentication.";
          case auth-key-chain {
            leaf key-chain {
              type key-chain:key-chain-ref;
              description
                "Specifies the name of the key chain.";
            }
          }
          case auth-key-explicit {
            leaf key-id {
              type uint32;
              description
                "Specifies a key identifier.";
            }
            leaf key {
              type string;
              description
                "OSPF authentication key.

                 This model only supports the subset of keys that
                 are representable as ASCII strings.";
            }
            leaf crypto-algorithm {
              type identityref {
                base key-chain:crypto-algorithm;
              }
              description
                "Indicates the cryptographic algorithm associated
                 with the key.";
            }
          }
        }
      }
    }
  }

  grouping isis-authentication {
    description
      "IS-IS authentication configuration.";
    container authentication {
      description
        "Container for IS-IS authentication parameters.";
      leaf enabled {
        type boolean;
        description
          "Enables or disables authentication.";
      }
      container keying-material {
        when "../enabled = 'true'";
        description
          "Describes how an IS-IS session is secured
           over an AC.";
        choice option {
          description
            "Options for IS-IS authentication.";
          case auth-key-chain {
            leaf key-chain {
              type key-chain:key-chain-ref;
              description
                "Specifies the name of the key chain.";
            }
          }
          case auth-key-explicit {
            leaf key-id {
              type uint32;
              description
                "Indicates a key identifier.";
            }
            leaf key {
              type string;
              description
                "IS-IS authentication key.

                 This model only supports the subset of keys that
                 are representable as ASCII strings.";
            }
            leaf crypto-algorithm {
              type identityref {
                base key-chain:crypto-algorithm;
              }
              description
                "Indicates the cryptographic algorithm associated
                 with the key.";
            }
          }
        }
      }
    }
  }

  grouping rip-authentication {
    description
      "RIP authentication configuration.";
    container authentication {
      description
        "Includes RIP authentication parameters.";
      leaf enabled {
        type boolean;
        description
          "Enables or disables authentication.";
      }
      container keying-material {
        when "../enabled = 'true'";
        description
          "Describes how a RIP session is to be secured
           on an AC.";
        choice option {
          description
            "Specifies the authentication scheme.";
          case auth-key-chain {
            leaf key-chain {
              type key-chain:key-chain-ref;
              description
                "Indicates the name of the key chain.";
            }
          }
          case auth-key-explicit {
            leaf key {
              type string;
              description
                "Specifies a RIP authentication key.

                 This model only supports the subset of keys that
                 are representable as ASCII strings.";
            }
            leaf crypto-algorithm {
              type identityref {
                base key-chain:crypto-algorithm;
              }
              description
                "Indicates the cryptographic algorithm associated
                 with the key.";
            }
          }
        }
      }
    }
  }

  // Basic routing parameters

  grouping bgp-peer-group-without-name {
    description
      "Identifies a BGP peer-group configured on the local system.";
    leaf local-as {
      type inet:as-number;
      description
        "Indicates a local AS Number (ASN). This ASN is exposed to
         a customer so that it knows which ASN to use to set up
         a BGP session.";
    }
    leaf peer-as {
      type inet:as-number;
      description
        "Indicates the customer's ASN when the customer requests
         BGP routing.";
    }
    leaf address-family {
      type identityref {
        base vpn-common:address-family;
      }
      description
        "This node contains the address families to be activated.
         'dual-stack' means that both IPv4 and IPv6 will be 
         activated.";
    }
    leaf role {
      type identityref {
        base ac-common:bgp-role;
      }
      description
        "Specifies the BGP role (provider, customer, peer, etc.).";
      reference
        "RFC 9234: Route Leak Prevention and Detection Using 
                   Roles in UPDATE and OPEN Messages, Section 4";
    }
  }

  grouping bgp-peer-group-with-name {
    description
      "Identifies a BGP peer-group configured on the local system -
       identified by a peer-group name.";
    leaf name {
      type string;
      description
        "Specifies the name of the BGP peer-group.";
    }
    uses bgp-peer-group-without-name;
  }

  grouping ospf-basic {
    description
      "Includes configuration specific to OSPF.";
    leaf address-family {
      type identityref {
        base vpn-common:address-family;
      }
      description
        "Indicates whether IPv4, IPv6, or both are to be activated.";
    }
    leaf area-id {
      type yang:dotted-quad;
      mandatory true;
      description
        "Specifies an area ID.";
      reference
        "RFC 4577: OSPF as the Provider/Customer Edge Protocol
                   for BGP/MPLS IP Virtual Private Networks
                   (VPNs), Section 4.2.3
         RFC 6565: OSPFv3 as a Provider Edge to Customer Edge
                   (PE-CE) Routing Protocol, Section 4.2";
    }
    leaf metric {
      type uint16;
      description
        "Metric of the AC. It is used in the routing state
         calculation and path selection.";
    }
  }

  grouping isis-basic {
    description
      "Basic configuration specific to IS-IS.";
    leaf address-family {
      type identityref {
        base vpn-common:address-family;
      }
      description
        "Indicates whether IPv4, IPv6, or both are to be activated.";
    }
    leaf area-address {
      type area-address;
      mandatory true;
      description
        "Specifies an area address.";
    }
  }

  // Static routing 

  grouping ipv4-static-rtg-entry {
    description
      "Parameters to configure a specific IPv4 static routing
       entry.";
    leaf lan {
      type inet:ipv4-prefix;
      description
        "Indicates an IPv4 LAN prefix.";
    }
    leaf lan-tag {
      type string;
      description
        "Internal tag to be used in service policies.";
    }
    leaf next-hop {
      type union {
        type inet:ip-address;
        type predefined-next-hop;
      }
      description
        "The next hop that is to be used for the static route.
         This may be specified as an IP address or a predefined
         next-hop type (e.g., 'discard' or 'local-link').";
    }
    leaf metric {
      type uint32;
      description
        "Indicates the metric associated with the static route.";
    }
  }

  grouping ipv4-static-rtg {
    description
      "A set of parameters specific to IPv4 static routing.";
    list ipv4-lan-prefixes {
      if-feature "vpn-common:ipv4";
      key "lan next-hop";
      description
        "List of LAN prefixes for the site.";
      uses ipv4-static-rtg-entry;
      uses ac-common:service-status;
    }
  }

  grouping ipv6-static-rtg-entry {
    description
      "Parameters to configure a specific IPv6 static routing
       entry.";
    leaf lan {
      type inet:ipv6-prefix;
      description
        "Indicates an IPv6 LAN prefix.";
    }
    leaf lan-tag {
      type string;
      description
        "Internal tag to be used in service (e.g., VPN) policies.";
    }
    leaf next-hop {
      type union {
        type inet:ip-address;
        type predefined-next-hop;
      }
      description
        "The next hop that is to be used for the static route.
         This may be specified as an IP address or a predefined
         next-hop type (e.g., 'discard' or 'local-link').";
    }
    leaf metric {
      type uint32;
      description
        "Indicates the metric associated with the static route.";
    }
  }

  grouping ipv6-static-rtg {
    description
      "A set of parameters specific to IPv6 static routing.";
    list ipv6-lan-prefixes {
      if-feature "vpn-common:ipv6";
      key "lan next-hop";
      description
        "List of LAN prefixes for the customer terminating points.";
      uses ipv6-static-rtg-entry;
      uses ac-common:service-status;
    }
  }

  // OAM

  grouping bfd {
    description
      "Groups a set of basic BFD parameters.";
    leaf holdtime {
      type uint32;
      units "milliseconds";
      description
        "Specifies the expected BFD holdtime.

         The customer may impose some fixed values for the
         holdtime period if the provider allows the customer
         to use this function.

         If the provider doesn't allow the customer to use
         this function, fixed values will not be set.";
      reference
        "RFC 5880: Bidirectional Forwarding Detection (BFD),
                   Section 6.8.18";
    }
  }

  // redundancy

  grouping redundancy-group {
    description
      "A grouping for redundancy group.";
    list group {
       key "group-id";
       description
         "Specifies a list of group identifiers.";
       leaf group-id {
         type string;
         description
           "Indicates the group-id to which an AC belongs.";
       }
       leaf precedence {
         type identityref {
           base ac-common:precedence-type;
         }
         description
           "Defines redundancy of an AC.";
       }
     }
   }

  // QoS

  grouping bandwidth-parameters {
    description
      "A grouping for bandwidth parameters.";
    leaf cir {
      type uint64;
      units "bps";
      description
        "Committed Information Rate (CIR). The maximum number of bits
         that a port can receive or send during one second over
         an interface.";
    }
    leaf cbs {
      type uint64;
      units "bytes";
      description
        "Committed Burst Size (CBS). CBS controls the bursty nature
         of the traffic. Traffic that does not use the configured
         CIR accumulates credits until the credits reach the
         configured CBS.";
    }
    leaf eir {
      type uint64;
      units "bps";
      description
        "Excess Information Rate (EIR), i.e., excess frame delivery
         allowed not subject to a Service Level Agreement (SLA).
         The traffic rate can be limited by EIR.";
    }
    leaf ebs {
      type uint64;
      units "bytes";
      description
        "Excess Burst Size (EBS). The bandwidth available for burst
         traffic from the EBS is subject to the amount of bandwidth
         that is accumulated during periods when traffic allocated
         by the EIR policy is not used.";
    }
    leaf pir {
      type uint64;
      units "bps";
      description
        "Peak Information Rate (PIR), i.e., maximum frame delivery
         allowed. It is equal to or less than sum of CIR and EIR.";
    }
    leaf pbs {
      type uint64;
      units "bytes";
      description
        "Peak Burst Size (PBS).";
    }
  }

  grouping bandwidth-per-type {
    description
      "Grouping for bandwidth per type.";
    list bandwidth {
      key "bw-type";
      description
        "List for bandwidth per type parameters.";
      leaf bw-type {
        type identityref {
          base vpn-common:bw-type;
        }
        description
          "Indicates the bandwidth type.";
      }
      choice type {
        description
          "Choice based upon bandwidth type.";
        case per-cos {
          description
            "Bandwidth per Class of Service (CoS).";
          list cos {
            key "cos-id";
            description
              "List of CoSes.";
            leaf cos-id {
              type uint8;
              description
                "Identifier of the CoS, indicated by a Differentiated
                 Services Code Point (DSCP) or a CE-CLAN CoS (802.1p)
                 value in the service frame.";
              reference
                "IEEE Std 802.1Q: Bridges and Bridged Networks";
            }
            uses bandwidth-parameters;
          }
        }
        case other {
          description
            "Other bandwidth types.";
          uses bandwidth-parameters;
        }
      }
    }
  }
}
