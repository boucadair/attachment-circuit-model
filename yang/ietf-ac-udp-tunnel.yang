module ietf-ac-udp-tunnel {
  yang-version 1.1;
  namespace "urn:ietf:params:xml:ns:yang:ietf-ac-udp-tunnel";
  prefix ac-udpt;

  import ietf-ac-common {
    prefix ac-common;
    reference
      "RFC SSSS: YANG Data Models for Bearers and 'Attachment
                 Circuits'-as-a-Service (ACaaS)";
  }
  import ietf-ac-svc {
    prefix ac-svc;
    reference
      "RFC SSSS: YANG Data Models for Bearers and 'Attachment
                 Circuits'-as-a-Service (ACaaS)";
  }
  import ietf-packet-fields {
    prefix packet-fields;
      reference
        "RFC 8519: YANG Data Model for Network Access
                   Control Lists (ACLs), Section 4.2";
  }

  organization
    "IETF DMM (Distributed Mobility Management)";
  contact
    "WG Web:   <https://datatracker.ietf.org/wg/dmm/>
     WG List:  <mailto:dmm@ietf.org>

     Author:   Mohamed Boucadair
               <mailto:mohamed.boucadair@orange.com>";
  description
    "This YANG module defines a YANG model for augmenting the ACaaS
     service model with UDP Encapsulation as Layer 3 tunnel service.

     Copyright (c) 2024 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see the
     RFC itself for full legal notices.";

  revision 2023-11-13 {
    description
      "Initial revision.";
    reference
      "RFC XXXX: Mobility-aware Transport Network Slicing for 5G";
  }

  identity udp {
    base ac-common:l3-tunnel-type;
    description
      "UDP Encapsulation.";
    reference
      "RFC 8085: UDP Usage Guidelines, Section 3.1.11";
  }

  augment "/ac-svc:attachment-circuits/ac-svc:ac"
        + "/ac-svc:ip-connection/ac-svc:l3-service"
        + "/ac-svc:l3-tunnel-service/ac-svc:l3-tunnel-service" {
    when "derived-from-or-self(./type, 'ac-udpt:udp')" {
      description
        "Only applicable if L3 service type is UDP encapsualtion.";
    }
    description
      "Augments Layer 3 AC service with required data nodes for
       UDP encapsulation support.";
     choice udp-port {
       description
         "Choice of specifying the source port number or referring
          to a group of port numbers.";
       container source-port-range-or-operator {
         description
            "Indicates a set of source ports numbers.";
         uses packet-fields:port-range-or-operator;
      }
    }
  }
}
